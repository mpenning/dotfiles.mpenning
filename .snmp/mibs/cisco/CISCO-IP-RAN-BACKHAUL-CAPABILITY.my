-- *****************************************************************
-- CISCO-IP-RAN-BACKHAUL-CAPABILITY.my: IP RAN backhaul optimization
-- capability MIB
--   
-- September 2005, John Linton
--   
-- Copyright (c) 2005, 2007 by cisco Systems Inc.
-- All rights reserved.
-- ****************************************************************

CISCO-IP-RAN-BACKHAUL-CAPABILITY DEFINITIONS ::= BEGIN

IMPORTS
    MODULE-IDENTITY
        FROM SNMPv2-SMI
    AGENT-CAPABILITIES
        FROM SNMPv2-CONF
    ciscoAgentCapability
        FROM CISCO-SMI;


ciscoIpRanBhCapability MODULE-IDENTITY
    LAST-UPDATED    "200509150000Z"
    ORGANIZATION    "Cisco Systems, Inc."
    CONTACT-INFO
            "Cisco Systems
            Customer Service

            Postal: 170 West Tasman Drive
            San Jose, CA  95134
            USA

            Tel: +1 800 553-NETS

            E-mail: cs-ran-o@cisco.com"
    DESCRIPTION
        "Agent capabilities for the
        CISCO-IP-RAN-BACKHAUL-MIB."
    REVISION        "200509150000Z"
    DESCRIPTION
        "Initial version of this MIB module."
    ::= { ciscoAgentCapability 999999 }



ciscoIpRanBhCapabilityV12R0402MR AGENT-CAPABILITIES
    PRODUCT-RELEASE "Cisco IOS 12.4(2)MR1."
    STATUS          current
    DESCRIPTION
        "IOS 12.4(2)MR1 Cisco CISCO-IP-RAN-BACKHAUL-MIB
        User Agent MIB capabilities."

    SUPPORTS        CISCO-IP-RAN-BACKHAUL-MIB
    INCLUDES        {
                        ciscoIpRanBackHaulScalarsGroup,
                        ciscoIpRanBackHaulConfigGroup,
                        ciscoIpRanBackHaulStatsGroup,
                        ciscoIpRanBackHaulAlarmGroup,
                        ciscoIpRanBackHaulErrorsGroup,
                        ciscoIpRanBackHaulHistoryGroup,
                        ciscoIpRanBackHaulNotifGroup
                    }
    VARIATION       cirbhBackHaulStatsInterval
    ACCESS          read-only
    DESCRIPTION
        "read-write access is not supported."

    VARIATION       cirbhBackHaulStatsEntries
    ACCESS          read-only
    DESCRIPTION
        "read-write access is not supported."

    ::= { ciscoIpRanBhCapability 1 }

END
