-- *****************************************************************
-- CISCO-BRIDGE-EXT-CAPABILITY.my
-- CISCO-BRIDGE-EXT-MIB agent capabilities
--   
-- October 2005, Guichuan Tang
--   
-- Copyright (c) 2005, 2007 by Cisco Systems, Inc.
-- All rights reserved.
-- *****************************************************************

CISCO-BRIDGE-EXT-CAPABILITY DEFINITIONS ::= BEGIN

IMPORTS
    MODULE-IDENTITY
        FROM SNMPv2-SMI
    AGENT-CAPABILITIES
        FROM SNMPv2-CONF
    ciscoAgentCapability
        FROM CISCO-SMI;


ciscoBridgeExtCapability MODULE-IDENTITY
    LAST-UPDATED    "200707030000Z"
    ORGANIZATION    "Cisco Systems, Inc."
    CONTACT-INFO
            "Cisco Systems
            Customer Service

            Postal: 170 West Tasman Drive
            San Jose, CA  95134
            USA

            Tel: +1 800 553-NETS

            E-mail: cs-lan-switch-snmp@cisco.com"
    DESCRIPTION
        "Agent capabilities for CISCO-BRIDGE-EXT-MIB."
    REVISION        "200707030000Z"
    DESCRIPTION
        "Added cbeCapV12R0233SXHPCat6K for Cisco IOS
        12.2(33)SXH."
    REVISION        "200510200000Z"
    DESCRIPTION
        "Initial version of this MIB module."
    ::= { ciscoAgentCapability 459 }



cbeCapV12R0218SXEPCat6K AGENT-CAPABILITIES
    PRODUCT-RELEASE "Cisco IOS 12.2(18)SXE on Catalyst 6000/6500
                         and Cisco 7600 series devices."
    STATUS          current
    DESCRIPTION
        "CISCO-BRIDGE-EXT-MIB agent capabilities."

    SUPPORTS        CISCO-BRIDGE-EXT-MIB
    INCLUDES        {
                        cbeDot1dTpGroup,
                        cbeDot1dTpVlanGroup
                    }
    VARIATION       cbeDot1dTpVlanRowStatus
    SYNTAX          INTEGER  {
                        active(1),
                        createAndGo(4),
                        destroy(6)
                    }
    DESCRIPTION
        "Only limited set of enumerated values are
        supported."

    ::= { ciscoBridgeExtCapability 1 }

cbeCapV12R0233SXHPCat6K AGENT-CAPABILITIES
    PRODUCT-RELEASE "Cisco IOS 12.2(33)SXH on Catalyst 6000/6500
                         series devices."
    STATUS          current
    DESCRIPTION
        "CISCO-BRIDGE-EXT-MIB agent capabilities."

    SUPPORTS        CISCO-BRIDGE-EXT-MIB
    INCLUDES        {
                        cbeDot1dTpGroup,
                        cbeDot1dTpVlanGroup,
                        cbeDot1dStaticGroup
                    }
    VARIATION       cbeDot1dTpVlanRowStatus
    SYNTAX          INTEGER  {
                        active(1),
                        createAndGo(4),
                        destroy(6)
                    }
    DESCRIPTION
        "Only limited set of enumerated values are
        supported."

    VARIATION       cbeDot1dStaticStatus
    SYNTAX          INTEGER  {
                        invalid(2),
                        deleteOnReset(4)
                    }
    DESCRIPTION
        "Only limited set of enumerated values are
        supported."

    ::= { ciscoBridgeExtCapability 2 }

END
