-- *****************************************************************
-- CISCO-SLB-EXT-CAPABILITY.my:
-- Cisco CISCO-SLB-EXT-MIB AGENT-CAPABILITIES
--
-- Jan 2006, Roopeshakumar N. Shalgar
--
-- Copyright (c) 2006 by Cisco Systems, Inc.
-- All rights reserved.
-- *****************************************************************

CISCO-SLB-EXT-CAPABILITY DEFINITIONS ::= BEGIN

IMPORTS
        MODULE-IDENTITY
                FROM SNMPv2-SMI
        AGENT-CAPABILITIES
                FROM SNMPv2-CONF
        ciscoAgentCapability
                FROM CISCO-SMI;

ciscoSlbExtCapability MODULE-IDENTITY
        LAST-UPDATED    "200602210000Z"
        ORGANIZATION    "Cisco Systems, Inc."
        CONTACT-INFO
                "       Cisco Systems
                        Customer Service

                Postal: 170 West Tasman Drive
                        San Jose, CA  95134
                        USA

                   Tel: +1 800 553-NETS

                E-mail: cs-slb@cisco.com"

        DESCRIPTION
                "The capabilities description of 
                 CISCO-SLB-EXT-MIB."
        REVISION        "200602210000Z"
        DESCRIPTION
                "Added capability statement 
                 ciscoSlbExtCapabilityACSWV03R000 for 
                 Application Control Engine (ACE)."
        ::= { ciscoAgentCapability 496 }

ciscoSlbExtCapabilityACSWV03R000 AGENT-CAPABILITIES

PRODUCT-RELEASE "ACSW (Application Control Software) 3.0"
STATUS          current
DESCRIPTION     "ACSW (Application Control Software) 3.0
                 CISCO SLB MIB capabilities"
SUPPORTS        CISCO-SLB-EXT-MIB
  INCLUDES      { cslbxStatsGroup, cslbxServerFarmsGroup, 
                  cslbxServerFarmsExtGroup, cslbxStatsHCGroup
                }

  VARIATION cslbxStatsServerInitConns
    ACCESS    not-implemented
    DESCRIPTION "Not supported."

  VARIATION cslbxStatsServerInitHCConns
    ACCESS    not-implemented
    DESCRIPTION "Not supported."

  VARIATION cslbxStatsCurrServerInitConns
    ACCESS    not-implemented
    DESCRIPTION "Not supported."

  VARIATION cslbxStatsFailedServerInitConns
    ACCESS    not-implemented
    DESCRIPTION "Not supported."

  VARIATION cslbxStatsNoActiveServerRejects
    ACCESS    not-implemented
    DESCRIPTION "Not supported."

  VARIATION cslbxServerFarmHashMaskAddrType
    ACCESS    read-only
    DESCRIPTION "Create operation not allowed."

  VARIATION cslbxServerFarmHashMaskAddr
    ACCESS    read-only
    DESCRIPTION "Create operation not allowed."

  VARIATION cslbxServerFarmClientNatPool
    ACCESS    not-implemented
    DESCRIPTION "Not supported."

  VARIATION cslbxServerFarmFailAction
    ACCESS    read-only
    DESCRIPTION "Create operation not allowed."

  VARIATION cslbxServerFarmHttpReturnCodeMap
    ACCESS    not-implemented
    DESCRIPTION "Not supported."

  VARIATION cslbxServerFarmInFailedThreshold
    ACCESS    not-implemented
    DESCRIPTION "Not supported."

  VARIATION cslbxServerFarmInbandResetTimer
    ACCESS    read-only
    DESCRIPTION "Create operation not allowed."

  VARIATION cslbxRedirectSvrRelocationStr
    ACCESS    not-implemented
    DESCRIPTION "Not supported."

  VARIATION cslbxRedirectSvrBackupString
    ACCESS    not-implemented
    DESCRIPTION "Not supported."

  VARIATION cslbxRedirectSvrRedirectCode
    ACCESS    not-implemented
    DESCRIPTION "Not supported."

  VARIATION cslbxRedirectSvrRedirectPort
    ACCESS    not-implemented
    DESCRIPTION "Not supported."

  VARIATION cslbxRedirectSvrState
    ACCESS    not-implemented
    DESCRIPTION "Not supported."

  VARIATION cslbxRedirectSvrNumberOfConns
    ACCESS    not-implemented
    DESCRIPTION "Not supported."

  VARIATION cslbxRedirectSvrMaxConns
    ACCESS    not-implemented
    DESCRIPTION "Not supported."

  VARIATION cslbxRedirectSvrAdminWeight
    ACCESS    not-implemented
    DESCRIPTION "Not supported."

  VARIATION cslbxRedirectSvrOperWeight
    ACCESS    not-implemented
    DESCRIPTION "Not supported."

  VARIATION cslbxRedirectSvrMetric
    ACCESS    not-implemented
    DESCRIPTION "Not supported."

  VARIATION cslbxRedirectSvrTotalConns
    ACCESS    not-implemented
    DESCRIPTION "Not supported."

  VARIATION cslbxRedirectSvrHCTotalConns
    ACCESS    not-implemented
    DESCRIPTION "Not supported."

  VARIATION cslbxRedirectSvrRowStatus
    ACCESS    not-implemented
    DESCRIPTION "Not supported."

  VARIATION cslbxServerFarmProbeRowStatus
    ACCESS    read-only
    DESCRIPTION "Create operation not allowed."

  VARIATION cslbxServerFarmTransparent
    ACCESS    read-only
    DESCRIPTION "Create operation not allowed."

  VARIATION cslbxServerFarmSlowStart
    ACCESS    read-only
    DESCRIPTION "Create operation not allowed."

  VARIATION cslbxServerFarmHashHeaderName
    ACCESS    read-only
    DESCRIPTION "Create operation not allowed."

  VARIATION cslbxServerFarmHashCookieName
    ACCESS    read-only
    DESCRIPTION "Create operation not allowed."

  VARIATION cslbxServerFarmUrlPatternBegin
    ACCESS    read-only
    DESCRIPTION "Create operation not allowed."

  VARIATION cslbxServerFarmUrlPatternEnd
    ACCESS    read-only
    DESCRIPTION "Create operation not allowed."

  VARIATION cslbxServerFarmDescription
    ACCESS    read-only
    DESCRIPTION "Create operation not allowed."

  VARIATION cslbxServerFarmType
    ACCESS    read-only
    DESCRIPTION "Create operation not allowed."

    ::= { ciscoSlbExtCapability 1 }

END
