-- *****************************************************************
-- CISCO-DYNAMIC-ARP-INSPECTION-CAPABILITY.my:
-- Cisco CISCO-DYNAMIC-ARP-INSPECTION-MIB AGENT-CAPABILITIES
--
-- January 2004, Edward Pham 
--
-- Copyright (c) 2004, 2007 by Cisco Systems, Inc.
-- All rights reserved.
-- *****************************************************************

CISCO-DYNAMIC-ARP-INSPECTION-CAPABILITY DEFINITIONS ::= BEGIN

IMPORTS
        MODULE-IDENTITY, Unsigned32
                FROM SNMPv2-SMI

        AGENT-CAPABILITIES
                FROM SNMPv2-CONF

        ciscoAgentCapability
                FROM CISCO-SMI;

ciscoDynamicArpInspCapability MODULE-IDENTITY
        LAST-UPDATED    "200707020000Z"
        ORGANIZATION    "Cisco Systems, Inc."
        CONTACT-INFO
                "       Cisco Systems
                        Customer Service

                Postal: 170 West Tasman Drive
                        San Jose, CA  95134
                        USA

                   Tel: +1 800 553-NETS

                E-mail: cs-lan-switch-snmp@cisco.com"
        DESCRIPTION
                "The capabilities description of
                 CISCO-DYNAMIC-ARP-INSPECTION-MIB."

        REVISION        "200707020000Z"
        DESCRIPTION
                "Added cdaiCapV12R0233SXHPCat6k agent
                 capability statement."

        REVISION        "200401130000Z"
        DESCRIPTION
                "Initial version of this MIB module."
        ::= { ciscoAgentCapability 382 }

cdaiCapabilityCatOSV08R0301Cat6k AGENT-CAPABILITIES
    PRODUCT-RELEASE      "Cisco CatOS 8.3(1) on Catalyst 6000/6500
                          and Cisco 7600 series devices."
    STATUS               current
    DESCRIPTION         "CISCO-DYNAMIC-ARP-INSPECTION-MIB capabilities."
 
    SUPPORTS             CISCO-DYNAMIC-ARP-INSPECTION-MIB
        INCLUDES         { cdaiVlanConfigGroup, 
                           cdaiGlobalLoggingGroup,
                           cdaiIfConfigGroup }

        VARIATION        cdaiVlanDynArpInspEnable 
            DESCRIPTION
                   "Only support false(2) on management VLAN 1."

    ::= { ciscoDynamicArpInspCapability 1 }

cdaiCapV12R0233SXHPCat6k AGENT-CAPABILITIES
    PRODUCT-RELEASE     "Cisco IOS 12.2(33)SXH on Catalyst 6000/6500
                         series devices."
    STATUS               current
    DESCRIPTION         "CISCO-DYNAMIC-ARP-INSPECTION-MIB capabilities."
 
    SUPPORTS            CISCO-DYNAMIC-ARP-INSPECTION-MIB
        INCLUDES        { cdaiVlanConfigGroup, 
                          cdaiIfConfigGroup,
                          cdaiIfRateLimitGroup }

        VARIATION       cdaiIfRateLimit
            SYNTAX      Unsigned32(0..2048 | 4294967295)
            DESCRIPTION "Only limited set of values are supported."

    ::= { ciscoDynamicArpInspCapability 2 }
END
